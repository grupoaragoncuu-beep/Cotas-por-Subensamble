' COTAS ABIGAIL - Prueba rapida de UNA cara
' Regla externa: COTAS_POR_SEG
'
' Equivalente a una sola etapa de COTAS_POR_SUBENSAMBLE:
'   SEGM1 | SEGM2 | SEGM3 | SEGM4 | TOP | BASE
'
' 1) Elige cual cara procesar.
' 2) Picks obligatorios:
'      - TOP COVER (mapeo / carpeta TOP)
'      - BASE (escuadra de camara desde piso/(0,0); OTC tiene tejado)
'      - la cara elegida si es SEGM*
' 3) Lanza generador_caras_tanque.py --seleccion <json> --solo <CARA>
'
' Salida: solo COTAS_POR_REFERENCIA\<CARA>\ (mas rapido para iterar).
'
' Rutas: NO hardcodear C:\Proyectos\...  Usar COTAS_ABIGAIL_DIR /
' config_planos.txt / ExternalRuleDirectories (instalador).

Imports System.Collections.Generic
Imports System.Text

Sub Main()
    Const kDrawingDocument As Integer = 12292

    Dim invApp As Inventor.Application = ThisApplication
    Dim titulo As String = "COTAS ABIGAIL - Cotas por SEG (prueba)"

    If invApp.ActiveDocument Is Nothing OrElse
       invApp.ActiveDocument.DocumentType <> kDrawingDocument Then
        System.Windows.Forms.MessageBox.Show(
            "Abre un plano (.idw / .dwg) y dejalo como ventana activa.",
            titulo,
            System.Windows.Forms.MessageBoxButtons.OK,
            System.Windows.Forms.MessageBoxIcon.Warning)
        Exit Sub
    End If

    Dim planoDoc As Document = invApp.ActiveDocument

    If String.IsNullOrWhiteSpace(planoDoc.FullDocumentName) Then
        System.Windows.Forms.MessageBox.Show(
            "Guarda el plano antes de ejecutar (necesario para exportar JPG).",
            titulo,
            System.Windows.Forms.MessageBoxButtons.OK,
            System.Windows.Forms.MessageBoxIcon.Warning)
        Exit Sub
    End If

    Dim planosDirFinal As String = ResolverPlanosDir(invApp)
    If String.IsNullOrWhiteSpace(planosDirFinal) Then
        System.Windows.Forms.MessageBox.Show(
            "No se encontro la carpeta Planos." & vbCrLf &
            "En esta PC ejecuta una vez:" & vbCrLf &
            "  Planos\instalar_boton_inventor.bat" & vbCrLf &
            "Luego cierra y vuelve a abrir Inventor.",
            titulo,
            System.Windows.Forms.MessageBoxButtons.OK,
            System.Windows.Forms.MessageBoxIcon.Error)
        Exit Sub
    End If

    Dim scriptPath As String =
        System.IO.Path.Combine(planosDirFinal, "generador_caras_tanque.py")

    If Not System.IO.File.Exists(scriptPath) Then
        System.Windows.Forms.MessageBox.Show(
            "No se encontro:" & vbCrLf & scriptPath,
            titulo,
            System.Windows.Forms.MessageBoxButtons.OK,
            System.Windows.Forms.MessageBoxIcon.Error)
        Exit Sub
    End If

    Dim asmDoc As AssemblyDocument = BuscarEnsambleTanque(invApp)
    If asmDoc Is Nothing Then
        System.Windows.Forms.MessageBox.Show(
            "Abre el ensamble (.iam) del tanque junto al machote.",
            titulo,
            System.Windows.Forms.MessageBoxButtons.OK,
            System.Windows.Forms.MessageBoxIcon.Warning)
        Exit Sub
    End If

    If EsProductoBoard(asmDoc) Then
        LanzarFlujoBoard(invApp, planosDirFinal, titulo)
        Exit Sub
    End If

    Dim caraElegida As String = InputBox( _
        "Cara a procesar (prueba rapida de UNA etapa):" & vbCrLf & vbCrLf & _
        "  SEGM1  SEGM2  SEGM3  SEGM4" & vbCrLf & _
        "  TOP    BASE" & vbCrLf & vbCrLf & _
        "Escribe exactamente una de esas etiquetas:", _
        titulo, _
        "SEGM1")
    If String.IsNullOrWhiteSpace(caraElegida) Then Exit Sub
    caraElegida = caraElegida.Trim().ToUpperInvariant()
    If caraElegida <> "SEGM1" AndAlso caraElegida <> "SEGM2" AndAlso _
       caraElegida <> "SEGM3" AndAlso caraElegida <> "SEGM4" AndAlso _
       caraElegida <> "TOP" AndAlso caraElegida <> "BASE" Then
        System.Windows.Forms.MessageBox.Show( _
            "Etiqueta no valida: " & caraElegida & vbCrLf & _
            "Usa SEGM1, SEGM2, SEGM3, SEGM4, TOP o BASE.", _
            titulo, _
            System.Windows.Forms.MessageBoxButtons.OK, _
            System.Windows.Forms.MessageBoxIcon.Warning)
        Exit Sub
    End If

    Const lenToMm As Double = 10.0
    Dim preBoxCm As Double() = CombinedRootOccurrenceRangeBoxCm(asmDoc)
    Dim pivotMm As Double() = Vec( _
        preBoxCm(6) * lenToMm, _
        preBoxCm(7) * lenToMm, _
        preBoxCm(8) * lenToMm)

    Dim pasoCara As String
    If caraElegida.StartsWith("SEGM") Then
        pasoCara = "3. Selecciona la cara expuesta de " & caraElegida & "."
    ElseIf caraElegida = "TOP" Then
        pasoCara = "3. (TOP ya cubierto con el pick 1.)"
    Else
        pasoCara = "3. (BASE ya cubierta con el pick 2.)"
    End If

    System.Windows.Forms.MessageBox.Show( _
        "Prueba rapida: solo " & caraElegida & vbCrLf & vbCrLf & _
        "Picks obligatorios (en orden):" & vbCrLf & _
        "1. TOP COVER (mapeo de tapa)." & vbCrLf & _
        "2. BASE del tanque (escuadra la camara desde el piso/(0,0)." & vbCrLf & _
        "   NO uses Top Cover como 'arriba': OTC tiene inclinacion tipo tejado)." & vbCrLf & _
        pasoCara & vbCrLf & vbCrLf & _
        "El origen (0,0) de cada pared es la esquina inferior-izquierda" & vbCrLf & _
        "del muro (escuadra perfecta desde la base)." & vbCrLf & vbCrLf & _
        "Luego se exporta solo COTAS_POR_REFERENCIA\" & caraElegida & "\.", _
        titulo)

    Try
        asmDoc.Activate()
    Catch
    End Try

    Dim topPick As Object = PedirCaraPlana( _
        invApp, "1/3 Selecciona el TOP COVER (tapa / mapeo)", pivotMm, lenToMm, "TOP")
    If topPick Is Nothing Then
        ReactivarPlano(planoDoc)
        Exit Sub
    End If

    Dim basePick As Object = PedirCaraPlana( _
        invApp, _
        "2/3 Selecciona la BASE (escuadra desde piso; obligatorio)", _
        pivotMm, _
        lenToMm, _
        "BASE")
    If basePick Is Nothing Then
        System.Windows.Forms.MessageBox.Show( _
            "La BASE es obligatoria: sin ella la camara se inclina con el tejado OTC" & vbCrLf & _
            "y las cotas TYP se descuadran.", _
            titulo, _
            System.Windows.Forms.MessageBoxButtons.OK, _
            System.Windows.Forms.MessageBoxIcon.Warning)
        ReactivarPlano(planoDoc)
        Exit Sub
    End If

    Dim segmentos As New List(Of Object)

    If caraElegida.StartsWith("SEGM") Then
        Dim segPick As Object = PedirCaraPlana( _
            invApp, _
            "3/3 Selecciona la cara expuesta de " & caraElegida, _
            pivotMm, _
            lenToMm, _
            caraElegida)
        If segPick Is Nothing Then
            ReactivarPlano(planoDoc)
            Exit Sub
        End If
        segmentos.Add(segPick)
    End If
    ' TOP / BASE: ya seleccionados arriba.

    If Not ValidarPicksDistintos(topPick, segmentos, basePick) Then
        ReactivarPlano(planoDoc)
        Exit Sub
    End If

    ReactivarPlano(planoDoc)

    Dim jsonPath As String = System.IO.Path.Combine( _
        planosDirFinal, "seleccion_caras.json")
    Try
        GuardarSeleccionJsonSolo( _
            jsonPath, _
            asmDoc.DisplayName, _
            preBoxCm, _
            topPick, _
            segmentos, _
            basePick, _
            caraElegida)
    Catch ex As Exception
        System.Windows.Forms.MessageBox.Show(
            "No se pudo guardar la seleccion:" & vbCrLf & ex.Message,
            titulo,
            System.Windows.Forms.MessageBoxButtons.OK,
            System.Windows.Forms.MessageBoxIcon.Error)
        Exit Sub
    End Try

    Dim pythonExeFinal As String = ResolverPythonExe(planosDirFinal)

    Dim psi As New System.Diagnostics.ProcessStartInfo()
    psi.FileName = pythonExeFinal
    psi.Arguments = """" & scriptPath & """ --seleccion """ & jsonPath & _
        """ --solo " & caraElegida
    psi.WorkingDirectory = planosDirFinal
    psi.UseShellExecute = False
    psi.CreateNoWindow = False

    Try
        Dim proceso As System.Diagnostics.Process =
            System.Diagnostics.Process.Start(psi)
        proceso.WaitForExit()

        If proceso.ExitCode = 0 Then
            System.Windows.Forms.MessageBox.Show(
                "Cara " & caraElegida & " generada." & vbCrLf &
                "Revisa Planos\JPG\<tanque>\COTAS_POR_REFERENCIA\" & caraElegida & "\.",
                titulo,
                System.Windows.Forms.MessageBoxButtons.OK,
                System.Windows.Forms.MessageBoxIcon.Information)
        Else
            System.Windows.Forms.MessageBox.Show(
                "El proceso termino con errores." & vbCrLf &
                "Revisa los mensajes de la ventana CMD.",
                titulo,
                System.Windows.Forms.MessageBoxButtons.OK,
                System.Windows.Forms.MessageBoxIcon.Warning)
        End If
    Catch ex As Exception
        System.Windows.Forms.MessageBox.Show(
            "No se pudo lanzar Python:" & vbCrLf & ex.Message & vbCrLf &
            "Python resuelto: " & pythonExeFinal,
            titulo,
            System.Windows.Forms.MessageBoxButtons.OK,
            System.Windows.Forms.MessageBoxIcon.Error)
    End Try
End Sub

' ------------------------------------------------------------
' Seleccion de caras (Dictionary para evitar Class en iLogic)
' ------------------------------------------------------------

Function PedirCaraPlana( _
    invApp As Inventor.Application, _
    prompt As String, _
    pivotMm As Double(), _
    lenToMm As Double, _
    etiqueta As String) As Object

    Dim obj As Object = invApp.CommandManager.Pick( _
        SelectionFilterEnum.kPartFacePlanarFilter, _
        prompt)

    If obj Is Nothing Then Return Nothing

    Dim face As FaceProxy = TryCast(obj, FaceProxy)
    If face Is Nothing Then
        System.Windows.Forms.MessageBox.Show( _
            "Selecciona una cara plana del ensamble.", _
            "COTAS ABIGAIL", _
            System.Windows.Forms.MessageBoxButtons.OK, _
            System.Windows.Forms.MessageBoxIcon.Warning)
        Return Nothing
    End If

    Dim occName As String = ""
    Try
        occName = face.ContainingOccurrence.Name
    Catch
        occName = ""
    End Try

    Dim puntoMm As Double() = FacePointMm(face, lenToMm)
    Dim nImported As Double() = FaceNormal(face)
    Dim normal As Double() = NormalizeVec( _
        ForceNormalAwayFromPivot(nImported, puntoMm, pivotMm))
    Dim vertices As List(Of Double()) = FaceVerticesMm(face, lenToMm)

    Dim data As New Dictionary(Of String, Object)
    data("etiqueta") = etiqueta
    data("occ_name") = occName
    data("normal") = normal
    data("punto_mm") = puntoMm
    data("vertices_mm") = vertices
    Return data
End Function

Function ValidarPicksDistintos( _
    topPick As Object, _
    segmentos As List(Of Object), _
    basePick As Object) As Boolean

    ' BASE y TOP no pueden ser la misma ocurrencia.
    If topPick IsNot Nothing AndAlso basePick IsNot Nothing Then
        Dim nTop As String = CStr(CType(topPick, Dictionary(Of String, Object))("occ_name")).Trim().ToUpperInvariant()
        Dim nBase As String = CStr(CType(basePick, Dictionary(Of String, Object))("occ_name")).Trim().ToUpperInvariant()
        If nTop <> "" AndAlso nTop = nBase Then
            System.Windows.Forms.MessageBox.Show( _
                "TOP COVER y BASE apuntan a la misma ocurrencia (" & nTop & ")." & vbCrLf & _
                "Vuelve a seleccionar: tapa arriba y placa de piso abajo.", _
                "COTAS ABIGAIL", _
                System.Windows.Forms.MessageBoxButtons.OK, _
                System.Windows.Forms.MessageBoxIcon.Warning)
            Return False
        End If
    End If

    Return True
End Function

Sub ReactivarPlano(planoDoc As Document)
    Try
        planoDoc.Activate()
    Catch
    End Try
End Sub

Function BuscarEnsambleTanque(invApp As Inventor.Application) As AssemblyDocument
    Dim mejor As AssemblyDocument = Nothing
    Dim mayor As Integer = -1
    Dim doc As Document
    For Each doc In invApp.Documents
        Try
            If doc.DocumentType <> DocumentTypeEnum.kAssemblyDocumentObject Then
                Continue For
            End If
            Dim asm As AssemblyDocument = CType(doc, AssemblyDocument)
            Dim cantidad As Integer =
                asm.ComponentDefinition.Occurrences.AllLeafOccurrences.Count
            If cantidad > mayor Then
                mayor = cantidad
                mejor = asm
            End If
        Catch
        End Try
    Next
    Return mejor
End Function

' ------------------------------------------------------------
' JSON
' ------------------------------------------------------------

Sub GuardarSeleccionJsonSolo( _
    ruta As String, _
    ensambleNombre As String, _
    pivotCm As Double(), _
    topPick As Object, _
    segmentos As List(Of Object), _
    basePick As Object, _
    solo As String)

    Dim sb As New StringBuilder()
    sb.AppendLine("{")
    sb.AppendLine("  ""version"": 1,")
    sb.AppendLine("  ""solo"": " & JsonStr(solo) & ",")
    sb.AppendLine("  ""ensamble"": " & JsonStr(ensambleNombre) & ",")
    sb.AppendLine( _
        "  ""pivot_cm"": [" & _
        Fmt(pivotCm(6)) & ", " & Fmt(pivotCm(7)) & ", " & Fmt(pivotCm(8)) & "],")
    sb.AppendLine("  ""top"": " & FacePickToJson(topPick, "  ") & ",")
    sb.AppendLine("  ""segmentos"": [")
    Dim i As Integer
    For i = 0 To segmentos.Count - 1
        Dim coma As String = If(i < segmentos.Count - 1, ",", "")
        sb.AppendLine(FacePickToJson(segmentos(i), "    ") & coma)
    Next
    sb.AppendLine("  ],")
    If basePick IsNot Nothing Then
        sb.AppendLine("  ""base"": " & FacePickToJson(basePick, "  "))
    Else
        sb.AppendLine("  ""base"": null")
    End If
    sb.AppendLine("}")
    System.IO.File.WriteAllText(ruta, sb.ToString(), Encoding.UTF8)
End Sub

Sub GuardarSeleccionJson( _
    ruta As String, _
    ensambleNombre As String, _
    pivotCm As Double(), _
    topPick As Object, _
    segmentos As List(Of Object), _
    Optional basePick As Object = Nothing)

    GuardarSeleccionJsonSolo( _
        ruta, ensambleNombre, pivotCm, topPick, segmentos, basePick, "")
End Sub

Function FacePickToJson(pickObj As Object, indent As String) As String
    Dim pick As Dictionary(Of String, Object) =
        CType(pickObj, Dictionary(Of String, Object))
    Dim normal As Double() = CType(pick("normal"), Double())
    Dim puntoMm As Double() = CType(pick("punto_mm"), Double())
    Dim vertices As List(Of Double()) =
        CType(pick("vertices_mm"), List(Of Double()))

    Dim sb As New StringBuilder()
    sb.AppendLine("{")
    sb.AppendLine(indent & "  ""etiqueta"": " & JsonStr(CStr(pick("etiqueta"))) & ",")
    sb.AppendLine(indent & "  ""occ_name"": " & JsonStr(CStr(pick("occ_name"))) & ",")
    sb.AppendLine(indent & "  ""normal"": [" & _
        Fmt(normal(0)) & ", " & Fmt(normal(1)) & ", " & Fmt(normal(2)) & "],")
    sb.AppendLine(indent & "  ""punto_mm"": [" & _
        Fmt(puntoMm(0)) & ", " & Fmt(puntoMm(1)) & ", " & Fmt(puntoMm(2)) & "],")
    sb.AppendLine(indent & "  ""vertices_mm"": [")
    Dim i As Integer
    For i = 0 To vertices.Count - 1
        Dim v As Double() = vertices(i)
        Dim coma As String = If(i < vertices.Count - 1, ",", "")
        sb.AppendLine(indent & "    [" & Fmt(v(0)) & ", " & Fmt(v(1)) & ", " & Fmt(v(2)) & "]" & coma)
    Next
    sb.AppendLine(indent & "  ]")
    sb.Append(indent & "}")
    Return sb.ToString()
End Function

Function JsonStr(texto As String) As String
    If texto Is Nothing Then texto = ""
    texto = texto.Replace("\", "\\").Replace("""", "\""")
    Return """" & texto & """"
End Function

Function Fmt(valor As Double) As String
    Return valor.ToString("G17", System.Globalization.CultureInfo.InvariantCulture)
End Function

' ------------------------------------------------------------
' Helpers de cara / vectores (minimos, estilo PQart)
' ------------------------------------------------------------

Function CombinedRootOccurrenceRangeBoxCm(ByVal asmDoc As AssemblyDocument) As Double()
    Dim xmin As Double = Double.MaxValue
    Dim ymin As Double = Double.MaxValue
    Dim zmin As Double = Double.MaxValue
    Dim xmax As Double = Double.MinValue
    Dim ymax As Double = Double.MinValue
    Dim zmax As Double = Double.MinValue
    Dim found As Boolean = False

    For Each occ As ComponentOccurrence In asmDoc.ComponentDefinition.Occurrences
        Try
            Dim rb As Box = occ.RangeBox
            If rb.MinPoint.X < xmin Then xmin = rb.MinPoint.X
            If rb.MinPoint.Y < ymin Then ymin = rb.MinPoint.Y
            If rb.MinPoint.Z < zmin Then zmin = rb.MinPoint.Z
            If rb.MaxPoint.X > xmax Then xmax = rb.MaxPoint.X
            If rb.MaxPoint.Y > ymax Then ymax = rb.MaxPoint.Y
            If rb.MaxPoint.Z > zmax Then zmax = rb.MaxPoint.Z
            found = True
        Catch
        End Try
    Next

    If Not found Then
        Throw New Exception("No se pudo calcular el bounding box del ensamble.")
    End If

    Dim vals(8) As Double
    vals(0) = xmin : vals(1) = ymin : vals(2) = zmin
    vals(3) = xmax : vals(4) = ymax : vals(5) = zmax
    vals(6) = (xmin + xmax) / 2.0
    vals(7) = (ymin + ymax) / 2.0
    vals(8) = (zmin + zmax) / 2.0
    Return vals
End Function

Function FaceVerticesMm( _
    ByVal f As FaceProxy, _
    ByVal lenToMm As Double) As List(Of Double())

    Dim pts As New List(Of Double())
    Try
        For Each vObj As Object In f.Vertices
            Try
                Dim p As Point = vObj.Point
                pts.Add(Vec(p.X * lenToMm, p.Y * lenToMm, p.Z * lenToMm))
            Catch
            End Try
        Next
    Catch
    End Try

    If pts.Count = 0 Then
        Dim rb As Box = f.RangeBox
        Dim xs(1) As Double
        Dim ys(1) As Double
        Dim zs(1) As Double
        xs(0) = rb.MinPoint.X * lenToMm : xs(1) = rb.MaxPoint.X * lenToMm
        ys(0) = rb.MinPoint.Y * lenToMm : ys(1) = rb.MaxPoint.Y * lenToMm
        zs(0) = rb.MinPoint.Z * lenToMm : zs(1) = rb.MaxPoint.Z * lenToMm
        Dim ix, iy, iz As Integer
        For ix = 0 To 1
            For iy = 0 To 1
                For iz = 0 To 1
                    pts.Add(Vec(xs(ix), ys(iy), zs(iz)))
                Next
            Next
        Next
    End If
    Return pts
End Function

Function FacePointMm(ByVal f As FaceProxy, ByVal lenToMm As Double) As Double()
    Dim p As Point = Nothing
    Try
        Dim rb As Box = f.RangeBox
        p = rb.MidPoint
    Catch
        Dim pl As Plane = CType(f.Geometry, Plane)
        p = pl.RootPoint
    End Try
    Return Vec(p.X * lenToMm, p.Y * lenToMm, p.Z * lenToMm)
End Function

Function FaceNormal(ByVal f As FaceProxy) As Double()
    If Not TypeOf f.Geometry Is Plane Then
        Throw New Exception("La cara no es plana.")
    End If
    Dim p As Plane = CType(f.Geometry, Plane)
    Return NormalizeVec(Vec(p.Normal.X, p.Normal.Y, p.Normal.Z))
End Function

Function ForceNormalAwayFromPivot( _
    ByVal importedNormal As Double(), _
    ByVal facePointMm As Double(), _
    ByVal pivotMm As Double()) As Double()

    Dim outDir As Double() = SubVec(facePointMm, pivotMm)
    If VecLength(outDir) < 0.000001 Then
        Return NormalizeVec(importedNormal)
    End If
    outDir = NormalizeVec(outDir)
    Dim n As Double() = NormalizeVec(importedNormal)
    If DotVec(n, outDir) < 0 Then
        n = ScaleVec(n, -1.0)
    End If
    Return NormalizeVec(n)
End Function

Function Vec(ByVal x As Double, ByVal y As Double, ByVal z As Double) As Double()
    Dim v(2) As Double
    v(0) = x : v(1) = y : v(2) = z
    Return v
End Function

Function DotVec(ByVal a As Double(), ByVal b As Double()) As Double
    Return a(0) * b(0) + a(1) * b(1) + a(2) * b(2)
End Function

Function VecLength(ByVal a As Double()) As Double
    Return Math.Sqrt(DotVec(a, a))
End Function

Function NormalizeVec(ByVal a As Double()) As Double()
    Dim l As Double = VecLength(a)
    If l < 0.000000001 Then
        Throw New Exception("Vector cero.")
    End If
    Return Vec(a(0) / l, a(1) / l, a(2) / l)
End Function

Function ScaleVec(ByVal a As Double(), ByVal s As Double) As Double()
    Return Vec(a(0) * s, a(1) * s, a(2) * s)
End Function

Function SubVec(ByVal a As Double(), ByVal b As Double()) As Double()
    Return Vec(a(0) - b(0), a(1) - b(1), a(2) - b(2))
End Function

' ------------------------------------------------------------
' Resolucion de rutas Planos / Python (sin cambios de contrato)
' ------------------------------------------------------------

Function ResolverPlanosDir(invApp As Inventor.Application) As String
    Try
        Dim variable As String =
            System.Environment.GetEnvironmentVariable("COTAS_ABIGAIL_DIR")
        If Not String.IsNullOrWhiteSpace(variable) AndAlso
           System.IO.Directory.Exists(variable) AndAlso
           EsCarpetaPlanosValida(variable) Then
            Return variable
        End If
    Catch
    End Try

    Dim desdeCfg As String = LeerPlanosDirDesdeConfigCandidatos(invApp)
    If Not String.IsNullOrWhiteSpace(desdeCfg) Then
        Return desdeCfg
    End If

    Dim desdeExt As String = BuscarPlanosEnExternalRuleDirs(invApp)
    If Not String.IsNullOrWhiteSpace(desdeExt) Then
        Return desdeExt
    End If

    Return ""
End Function

Function EsCarpetaPlanosValida(dirPlanos As String) As Boolean
    Try
        If System.IO.File.Exists(System.IO.Path.Combine(dirPlanos, "generador_piezas.py")) Then Return True
        If System.IO.File.Exists(System.IO.Path.Combine(dirPlanos, "generador_tanque_completo.py")) Then Return True
        If System.IO.File.Exists(System.IO.Path.Combine(dirPlanos, "generador_caras_tanque.py")) Then Return True
    Catch
    End Try
    Return False
End Function

Function LeerValorConfig(cfgPath As String, clave As String) As String
    Try
        If Not System.IO.File.Exists(cfgPath) Then Return ""
        Dim prefijo As String = clave & "="
        For Each linea As String In System.IO.File.ReadAllLines(cfgPath)
            If linea.StartsWith(prefijo, StringComparison.OrdinalIgnoreCase) Then
                Return linea.Substring(prefijo.Length).Trim()
            End If
        Next
    Catch
    End Try
    Return ""
End Function

Function LeerPlanosDirDesdeConfigCandidatos(invApp As Inventor.Application) As String
    Dim candidatos As New System.Collections.Generic.List(Of String)

    Try
        Dim env As String =
            System.Environment.GetEnvironmentVariable("COTAS_ABIGAIL_DIR")
        If Not String.IsNullOrWhiteSpace(env) Then
            candidatos.Add(System.IO.Path.Combine(env, "ilogic\config_planos.txt"))
            candidatos.Add(System.IO.Path.Combine(env, "config_planos.txt"))
        End If
    Catch
    End Try

    Try
        Dim dirs = ObtenerExternalRuleDirectories(invApp)
        If dirs IsNot Nothing Then
            For Each d As String In dirs
                If String.IsNullOrWhiteSpace(d) Then Continue For
                candidatos.Add(System.IO.Path.Combine(d, "config_planos.txt"))
                Dim padre As String = System.IO.Path.GetDirectoryName(d)
                If Not String.IsNullOrWhiteSpace(padre) Then
                    candidatos.Add(System.IO.Path.Combine(padre, "ilogic\config_planos.txt"))
                    candidatos.Add(System.IO.Path.Combine(padre, "config_planos.txt"))
                End If
            Next
        End If
    Catch
    End Try

    For Each cfg As String In candidatos
        Try
            Dim valor As String = LeerValorConfig(cfg, "PLANOS_DIR")
            If Not String.IsNullOrWhiteSpace(valor) AndAlso
               System.IO.Directory.Exists(valor) AndAlso
               EsCarpetaPlanosValida(valor) Then
                Return valor
            End If
            Dim carpetaCfg As String = System.IO.Path.GetDirectoryName(cfg)
            If Not String.IsNullOrWhiteSpace(carpetaCfg) Then
                Dim posiblePlanos As String = System.IO.Path.GetDirectoryName(carpetaCfg)
                If EsCarpetaPlanosValida(posiblePlanos) Then Return posiblePlanos
                If EsCarpetaPlanosValida(carpetaCfg) Then Return carpetaCfg
            End If
        Catch
        End Try
    Next
    Return ""
End Function

Function ObtenerExternalRuleDirectories(invApp As Inventor.Application) As Object
    Try
        Dim iLogicAddIn As ApplicationAddIn =
            invApp.ApplicationAddIns.ItemById("{3BDD8D79-2179-4B11-8A5A-257B1C0263AC}")
        If iLogicAddIn Is Nothing Then Return Nothing
        If Not iLogicAddIn.Activated Then iLogicAddIn.Activate()
        Dim auto As Object = iLogicAddIn.Automation
        Return auto.FileOptions.ExternalRuleDirectories
    Catch
        Return Nothing
    End Try
End Function

Function BuscarPlanosEnExternalRuleDirs(invApp As Inventor.Application) As String
    Try
        Dim dirs = ObtenerExternalRuleDirectories(invApp)
        If dirs Is Nothing Then Return ""
        For Each d As String In dirs
            If String.IsNullOrWhiteSpace(d) Then Continue For
            If EsCarpetaPlanosValida(d) Then Return d
            Dim padre As String = System.IO.Path.GetDirectoryName(d)
            If EsCarpetaPlanosValida(padre) Then Return padre
        Next
    Catch
    End Try
    Return ""
End Function

Function ResolverPythonExe(planosDir As String) As String
    Dim cfgPath As String =
        System.IO.Path.Combine(planosDir, "ilogic\config_planos.txt")
    Dim valor As String = LeerValorConfig(cfgPath, "PYTHON_EXE")
    If Not String.IsNullOrWhiteSpace(valor) Then Return valor
    Return "python"
End Function

' ------------------------------------------------------------
' Desvío BOARD / GIGA tablero (sin picks de tanque)
' ------------------------------------------------------------

Function EsProductoBoard(asmDoc As AssemblyDocument) As Boolean
    Try
        Dim u As String =
            ("" & asmDoc.DisplayName & " " & asmDoc.FullFileName).ToUpperInvariant()
        If u.Contains("BOARD") Then Return True
        If System.Text.RegularExpressions.Regex.IsMatch(
            u, "\d{3,5}\s*[-_]?\s*BOARD") Then
            Return True
        End If
    Catch
    End Try
    Return False
End Function

Sub LanzarFlujoBoard( _
    invApp As Inventor.Application, _
    planosDirFinal As String, _
    titulo As String)

    Dim scriptPath As String =
        System.IO.Path.Combine(planosDirFinal, "generador_board.py")
    If Not System.IO.File.Exists(scriptPath) Then
        System.Windows.Forms.MessageBox.Show(
            "No se encontro generador_board.py en:" & vbCrLf & planosDirFinal,
            titulo,
            System.Windows.Forms.MessageBoxButtons.OK,
            System.Windows.Forms.MessageBoxIcon.Error)
        Exit Sub
    End If

    Dim pythonExeFinal As String = ResolverPythonExe(planosDirFinal)
    Dim psi As New System.Diagnostics.ProcessStartInfo()
    psi.FileName = pythonExeFinal
    psi.Arguments = """" & scriptPath & """"
    psi.WorkingDirectory = planosDirFinal
    psi.UseShellExecute = False
    psi.CreateNoWindow = False

    Try
        Dim proc As System.Diagnostics.Process =
            System.Diagnostics.Process.Start(psi)
        proc.WaitForExit()
        If proc.ExitCode = 0 Then
            System.Windows.Forms.MessageBox.Show(
                "Producto BOARD detectado: flujo tablero exportado." & vbCrLf &
                "Revisa Planos\JPG\<job>\BOARD\<kit>\FRONT|BACK|TOP|BOTTOM|RIGHT|LEFT\.",
                titulo,
                System.Windows.Forms.MessageBoxButtons.OK,
                System.Windows.Forms.MessageBoxIcon.Information)
        Else
            System.Windows.Forms.MessageBox.Show(
                "El flujo BOARD termino con errores. Revisa la ventana CMD.",
                titulo,
                System.Windows.Forms.MessageBoxButtons.OK,
                System.Windows.Forms.MessageBoxIcon.Warning)
        End If
    Catch ex As Exception
        System.Windows.Forms.MessageBox.Show(
            "No se pudo lanzar generador_board.py:" & vbCrLf & ex.Message,
            titulo,
            System.Windows.Forms.MessageBoxButtons.OK,
            System.Windows.Forms.MessageBoxIcon.Error)
    End Try
End Sub
